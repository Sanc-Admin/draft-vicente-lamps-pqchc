-- PQCHC-2026 ASN.1 Module
-- draft-vicente-lamps-pqchc-00
-- This module defines the PQCHCommitment extension syntax.
-- OID assignments are TBD pending IANA processing.
-- Experimental arc: 1.3.6.1.4.1.65953.1.1

PQCHC-2026
  { iso(1) identified-organization(3) dod(6) internet(1)
    security(5) mechanisms(5) pkix(7) id-mod(0) TBD1 }

DEFINITIONS IMPLICIT TAGS ::= BEGIN

IMPORTS
    EXTENSION
        FROM PKIX-CommonTypes-2009
            { iso(1) identified-organization(3) dod(6) internet(1)
              security(5) mechanisms(5) pkix(7) id-mod(0) 57 }
    AlgorithmIdentifier{}
        FROM PKIX1Algorithms2008
            { iso(1) identified-organization(3) dod(6) internet(1)
              security(5) mechanisms(5) pkix(7) id-mod(0) 45 }
    id-pe
        FROM PKIX1Explicit-2009
            { iso(1) identified-organization(3) dod(6) internet(1)
              security(5) mechanisms(5) pkix(7) id-mod(0) 51 } ;

-- Object Identifier for the PQCHC Extension
-- PRODUCTION: id-pe-pqchc ::= { id-pe TBD2 }
-- EXPERIMENTAL (PEN arc for Sanctum SecOps LLC):
id-pe-pqchc-experimental OBJECT IDENTIFIER ::=
    { 1 3 6 1 4 1 65953 1 1 }

-- The PQCHC Extension
ext-PQCHC EXTENSION ::= {
    SYNTAX        PQCHCommitment
    IDENTIFIED BY id-pe-pqchc-experimental }

-- Main Extension Structure
PQCHCommitment ::= SEQUENCE {
    commitmentValid      BOOLEAN,
    committedAlgorithm   AlgorithmIdentifier { ALGORITHM, {...} },
    futureKeyCommitment  FutureKeyCommitment OPTIONAL,
    commitmentNotAfter   GeneralizedTime,
    policyURI            IA5String OPTIONAL
}

-- Future Key Commitment Structure
FutureKeyCommitment ::= SEQUENCE {
    hashAlgorithm        AlgorithmIdentifier { DIGEST-ALGORITHM, {...} },
    spkiHash             OCTET STRING,
    keyAlgorithmHint     AlgorithmIdentifier { ALGORITHM, {...} } OPTIONAL
}

END
